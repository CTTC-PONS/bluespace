module tapi-bvt {
    namespace "urn:onf:otcc:yang:tapi-bvt";
    prefix tapi-bvt;
    import tapi-common {
        prefix tapi-common;
    }
    import tapi-connectivity {
        prefix tapi-connectivity;
    }
    import tapi-topology {
        prefix tapi-topology;
    }
    import tapi-photonic-media {
        prefix tapi-photonic-media;
    }
    organization "H2020 BlueSPACE";
    contact "";
    description "
        This module contains TAPI bvt Model definitions.
        ";
    revision 2019-10-24 {
        description "Based on ONF Transport API version 2.1.2.
                   Changes included in this TAPI release (v2.1.2)";
    }
    
       
    augment "/tapi-common:context/tapi-common:service-interface-point" {
        container bvt-service-interface-point-spec {
            uses bvt-service-interface-point-spec;
            description "none";
        }
        description "none";
    }

    augment "/tapi-common:context/tapi-topology:topology-context/tapi-topology:topology/tapi-topology:node/tapi-topology:node-edge-point/tapi-connectivity:cep-list/tapi-connectivity:connection-end-point" {
        container bvt-connection-end-point-spec {
            uses bvt-connection-end-point-spec;
            description "none";
        }
        description "none";
    }
    
   
    
   /**************************
    * package object-classes
    **************************/
    grouping bvt-connection-end-point-spec {
        container bvt-termination {
            config false;
            uses bvt-termination-pac;
	    description "Configured parameters of the BVT transceiver";
        }	
    }
	
    grouping bvt-termination-pac {
        container selected-central-frequency {
            config false;
            uses tapi-photonic-media:central-frequency;
            description "none";
        }
	container selected-spectrum {
            config false;
            uses tapi-photonic-media:spectrum-band; 
            description "none";
        }
        container selected-capacity {
            config false;
            uses tapi-common:capacity;
        }	
    }

    grouping bvt-service-interface-point-spec {
        container bvt-capability {
            config false;
            uses bvt-capability-pac;
            description "Capabilities of the BVT transceiver";
        }
    }

    grouping bvt-capability-pac {
        container supported-capacity {
            container max-capacity {
                uses tapi-common:capacity;
            }
            container min-capacity {
                uses tapi-common:capacity;
            }
        }			
    }	

 
    

   /**************************
    * package type-definitions
    **************************/
    identity PHOTONIC_LAYER_QUALIFIER_BVT {
        base tapi-common:LAYER_PROTOCOL_QUALIFIER;
        description "none";
    }
    
  
    
}
