module tapi-obfn {
    namespace "urn:onf:otcc:yang:tapi-obfn";
    prefix tapi-obfn;
    import tapi-common {
        prefix tapi-common;
    }
    import tapi-connectivity {
        prefix tapi-connectivity;
    }
    import tapi-topology {
        prefix tapi-topology;
    }
    import tapi-photonic-media {
        prefix tapi-photonic-media;
    }
    organization "CTTC";
    contact "";
    description "
        This module contains TAPI obfn Model definitions.
        ";
    revision 2010-10-24 {
        description "Based on ONF Transport API version 2.1.2.
                   Changes included in this TAPI release (v2.1.2)";
    }
    
       
    augment "/tapi-common:context/tapi-common:service-interface-point" {
        container obfn-service-interface-point-spec {
            uses obfn-service-interface-point-spec;
            description "none";
        }
        description "none";
    }

    augment "/tapi-common:context/tapi-topology:topology-context/tapi-topology:topology/tapi-topology:node/tapi-topology:owned-node-edge-point/tapi-connectivity:cep-list/tapi-connectivity:connection-end-point" {
        container obfn-connection-end-point-spec {
            config false;
            uses obfn-connection-end-point-spec;
            description "none";
        }
        description "none";
    }
    
    augment "/tapi-common:context/tapi-connectivity:connectivity-context/tapi-connectivity:connectivity-service" {
        container obfn-connectivity-constraint-spec {
            uses obfn-connectivity-constraint-spec;
            description "none";
        }
        description "none";
    }
    
   /**************************
    * package object-classes
    **************************/

    grouping obfn-params {
        container wavelength-reference {
            uses tapi-photonic-media:central-frequency;
            description "none";
        }
        list obfn-pool {
            key 'obfn-id';
            uses obfn;
            description "none";
        }
    }
	
    grouping obfn-connectivity-constraint-spec {	
        uses obfn-params;
    }	

    grouping obfn {
        leaf obfn-id{
            type uint64;
        }
        leaf beam_enable {
            type boolean;
        }
        leaf offset-angle-X {
            type uint64;
            description "[-90,90]";
        }
        leaf offset-angle-Y {
            type uint64;
            description "[-90,90]";
        }
        leaf width {
            type uint64;
        }
    }
	
    grouping obfn-connection-end-point-spec {
        uses obfn-params;
        description "none";
    }

    grouping obfn-service-interface-point-spec {
        container supported-wavelength {
            uses tapi-photonic-media:spectrum-band;
        } 
        leaf supported-beams {
            type uint64;
        }         
        leaf supported-upper-angle {
            type uint64;
        }
        leaf supported-lower-angle {
            type uint64;
        }	
        leaf supported-max-width {
            type uint64;
        }
        leaf supported-min-width {
            type uint64;
        }
        description "none";
    }

 
    

   /**************************
    * package type-definitions
    **************************/
    identity PHOTONIC_LAYER_QUALIFIER_OBFN {
        base tapi-common:LAYER_PROTOCOL_QUALIFIER;
        description "none";
    }
    
    
}
